module hfr-oc-tsn {

  // namespace
  namespace "urn:hfr:ns:hfr-oc-tsn";

  // prefix
  prefix "hfr-oc-tsn";

  // import some basic types
  import iana-if-type { prefix ift; }
  import hfr-oc-types { prefix hfr-oc-types; }
  import openconfig-yang-types { prefix oc-yang; }
  import openconfig-interfaces { prefix oc-if; }
  import openconfig-extensions { prefix oc-ext; }

  // meta
  organization "HFR,Inc. for Mobile Internet";

  contact 
      "HFR,Inc. for Mobile Internet

      Address: Hana EZ tower 5F, 10, Seongnam-daero 43 beon-gil,
        Bundang-gu, Seongnam-si, Gyeonggi-do, Korea
      Tel: 82-31-712-7768 (Fax: 82-31-712-7948)
      E-mail: resonant@hfrnet.com
      Web: hfrnet.com
      YANG desgined by: neoul@hfrnet.com";

  description
    "This module contains HFR NE TSN (Time Sensitive Networking)
    YANG model for OpenConfig.
    Copyright (c) 2019 HFR,Inc. All rights reserved. ";

  oc-ext:openconfig-version "0.1.1";

  revision "2020-06-01" {
    description
      "Inital model of HFR NE (Network Equipment) YANG model";
    reference "0.1.1";
  }

  // grouping statements

  grouping tsn-preemption-config {
    description
      "Top-level grouping for TSN preemption configuration
      associated with an Ethernet interface";

    leaf enable {
      type boolean;
      default false;
      description
        "Enables TSN preemption";
    }

    leaf express-queue {
      type hfr-oc-types:queue-range;
      description
        "Sets queues TSN preemption to queues.
        e.g. 6,7";
    }
  }

  grouping tsn-preemption-statistics {
    description
      "Top-level grouping for TSN preemption service statistics";
    
    container statistics {
      config false;
      description
        "A collection of preempted or non-preempted 
        traffic statistics";

      leaf out-mcast-pkts {
        type oc-yang:counter64;
      }
      leaf out-mcast-octets {
        type oc-yang:counter64;
      }
      leaf out-ucast-pkts {
        type oc-yang:counter64;
      }
      leaf out-ucast-octets {
        type oc-yang:counter64;
      }
      leaf out-mcast-drop-pkts {
        type oc-yang:counter64;
      }
      leaf out-mcast-drop-octets {
        type oc-yang:counter64;
      }
      leaf in-lossy-pkts-low {
        type oc-yang:counter64;
      }
      leaf in-lossy-pkts-high {
        type oc-yang:counter64;
      }
      leaf in-lossy-octets-low {
        type oc-yang:counter64;
      }
      leaf in-lossy-octets-high {
        type oc-yang:counter64;
      }
      leaf in-lossy-drop-pkts-low {
        type oc-yang:counter64;
      }
      leaf in-lossy-drop-pkts-high {
        type oc-yang:counter64;
      }
      leaf in-lossy-drop-octets-low {
        type oc-yang:counter64;
      }
      leaf in-lossy-drop-octets-high {
        type oc-yang:counter64;
      }
      leaf in-lossless-drop-pkts {
        type oc-yang:counter64;
      }
      leaf in-lossless-drop-octets {
        type oc-yang:counter64;
      }
      leaf in-lossless-pkts {
        type oc-yang:counter64;
      }
      leaf in-lossless-octets {
        type oc-yang:counter64;
      }
    }
  }

  grouping tsn-preemption-top {
    description
      "TSN preemption configuration associated with 
      an Ethernet interface";

    container preemption {
      description
        "Enclosing container for TSN interface-specific
        data on Ethernet interfaces.";
      uses tsn-preemption-config;
    }
  }

  grouping tsn-top {
    description
      "Top-level grouping for TSN data associated with 
      an Ethernet interface";
    container time-sensitive-networking {
      when "../oc-if:config/oc-if:type = 'ift:ethernetCsmacd'" {
      description 
        "Additional interface configuration parameters when
        the interface type is Ethernet";
      }

      container config {
        description "Configuration data for Time Sensitive Networking";
      }

      container state {

        config false;
        description "State variables for Time Sensitive Networking";

        uses tsn-preemption-top;
        uses tsn-preemption-statistics;
      }
    }
  }

  // data definition statements

  // If the module creates a top-level node in the schema
  // (e.g., at root level), there should be an instantiation of the
  // top-level '-top' grouping with a 'uses' statement.
  // uses example-top;

  // augment statements

  augment "/oc-if:interfaces/oc-if:interface" {
    description "Adds TSN configuration to interfaces model";
    uses tsn-top;
  }

  // If the module defines data that is added as an extension or
  // additional data to another module, use an augment statement
  // and instantiate the top-level grouping (or whichever grouping
  // is to be added to the other module) with a 'uses' statement
  // within the augment statement.

}
